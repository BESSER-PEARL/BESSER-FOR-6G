module _3gpp-nr-nrm-dmrofunction {
  yang-version 1.1;
  namespace "urn:3gpp:sa5:_3gpp-nr-nrm-dmrofunction";
  prefix "dmrofunction3gpp";

  import _3gpp-common-subnetwork { prefix subnet3gpp; }
  import _3gpp-common-top { prefix top3gpp; }
  import _3gpp-nr-nrm-gnbcucpfunction { prefix gnbcucp3gpp; }
  import _3gpp-common-managed-element { prefix me3gpp; }
  import _3gpp-nr-nrm-nrcellcu { prefix nrcellcu3gpp; }


  organization "3GPP SA5";
  contact "https://www.3gpp.org/DynaReport/TSG-WG--S5--officials.htm?Itemid=464";
  description "Defines the YANG mapping of the DMROFunction Information Object Class
    (IOC) that is part of the NR Network Resource Model (NRM).";
  reference "3GPP TS 28.541 5G Network Resource Model (NRM)";

  revision 2020-05-08 { reference S5-203316; }


  grouping DMROFunctionGrp {
    description "Represents the DMROFunction IOC.";
    reference "3GPP TS 28.541";
    uses top3gpp:Top_Grp;

    leaf maximumDeviationHoTrigger {
        description "This parameter defines the maximum allowed absolute deviation of the Handover Trigger, from the default point of operation.";
        type int32 { range "-20..20"; }
        units "0.5";
    }

    leaf minimumTimeBetweenHoTriggerChange {
        description "This parameter defines the minimum allowed time interval between two Handover Trigger change performed by MRO. This is used to control the stability and convergence of the algorithm.";
        type int32 { range "0..604800"; }
        units "1";
    }

    leaf tstoreUEcntxt {
        description "The timer used for detection of too early HO, too late HO and HO to wrong cell.";
        type int32 { range "0..1023"; }
        units "100";
    }


    leaf dmroControl {
        description " This attribute determines whether the MRO function is enabled or disabled.";
        type boolean;
    }

  }


  augment "/me3gpp:ManagedElement/gnbcucp3gpp:GNBCUCPFunction/nrcellcu3gpp:NRCellCU" {
    if-feature nrcellcu3gpp:DMROFunction;
    uses DMROFunctionGrp;
    }
  augment "/me3gpp:ManagedElement/gnbcucp3gpp:GNBCUCPFunction" {
    if-feature gnbcucp3gpp:DMROFunction;
    uses DMROFunctionGrp;
    }
  augment "/me3gpp:ManagedElement" {
    if-feature me3gpp:DMROFunction;
    uses DMROFunctionGrp;
    }
  augment "/subnet3gpp:SubNetwork" {
    if-feature subnet3gpp:DMROFunction;
    uses DMROFunctionGrp;
    }
}
