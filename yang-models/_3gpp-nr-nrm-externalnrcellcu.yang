module _3gpp-nr-nrm-externalnrcellcu {
  yang-version 1.1;
  namespace "urn:3gpp:sa5:_3gpp-nr-nrm-externalnrcellcu";
  prefix "extnrcellcu3gpp";

  import _3gpp-common-yang-types { prefix types3gpp; }
  import _3gpp-common-managed-function { prefix mf3gpp; }
  import _3gpp-nr-nrm-nrnetwork { prefix nrnet3gpp; }
  import _3gpp-common-subnetwork { prefix subnet3gpp; }
  import _3gpp-nr-nrm-externalgnbcucpfunction { prefix extgnbcucp3gpp; }
  import _3gpp-common-top { prefix top3gpp; }

  organization "3GPP SA5";
  description "Defines the YANG mapping of the ExternalNRCellCU Information
    Object Class (IOC), that is part of the NR Network Resource Model (NRM).";
  reference "3GPP TS 28.541 5G Network Resource Model (NRM)";

  revision 2019-10-28 { reference S5-193518 ; }
  
  revision 2019-06-17 {
    description "Initial revision";
  }

  grouping ExternalNRCellCUGrp {
    description "Represents the ExternalNRCellCU IOC."; 
    reference "3GPP TS 28.541";
    uses mf3gpp:ManagedFunctionGrp;
        
    leaf cellLocalId {       	
      description "Identifies an NR cell of a gNB. Together with corresponding
        gNB ID it forms the NR Cell Identifier (NCI).";
      reference "NCI in 3GPP TS 38.300";
      mandatory true;
      type int32 {range "0..16383"; }     	
    }

    leaf nRPCI {
      description "The Physical Cell Identity (PCI) of the NR cell.";
      reference "3GPP TS 36.211";
      mandatory true;
      type int32 { range "0..1007"; }
    }

    list pLMNIdList {
      description "Defines which PLMNs that are assumed to be served by the
        NR cell in another gNB CU-CP. This list is either updated by the
        managed element itself (e.g. due to ANR, signalling over Xn, etc.) or
        by consumer over the standard interface.";
      key "mcc mnc";
      min-elements 1;
      max-elements 12;
      uses types3gpp:PLMNId;
    }

    leaf nRFrequencyRef {
      description "Reference to corresponding NRFrequency instance.";
      mandatory true;
      type types3gpp:DistinguishedName;
    }
  }

  grouping ExternalNRCellCUWrapper {
    list ExternalNRCellCU {
      description "Represents the properties of an NRCellCU controlled by
        another Management Service Provider.";
      reference "3GPP TS 28.541";
      key id;
      uses top3gpp:Top_Grp;
      container attributes {
        uses ExternalNRCellCUGrp;
      }
      uses mf3gpp:ManagedFunctionContainedClasses;
    }
  } 
  
  augment "/subnet3gpp:SubNetwork/extgnbcucp3gpp:ExternalGNBCUCPFunction" {
    if-feature subnet3gpp:ExternalsUnderSubNetwork ;
    uses ExternalNRCellCUWrapper;
  }

  augment "/nrnet3gpp:NRNetwork/extgnbcucp3gpp:ExternalGNBCUCPFunction" {
    if-feature nrnet3gpp:ExternalsUnderNRNetwork;
    uses ExternalNRCellCUWrapper;
  }
}
