module _3gpp-5gc-nrm-neffunction {
  yang-version 1.1;
  
  namespace urn:3gpp:sa5:_3gpp-5gc-nrm-neffunction;
  prefix nef3gpp;
  
  import _3gpp-common-managed-function { prefix mf3gpp; }
  import _3gpp-common-managed-element { prefix me3gpp; }
  import ietf-inet-types { prefix inet; }
  import _3gpp-common-top { prefix top3gpp; }
  import _3gpp-5g-common-yang-types { prefix types5g3gpp; }
  
  organization "3gpp SA5";
  contact "https://www.3gpp.org/DynaReport/TSG-WG--S5--officials.htm?Itemid=464";
  description "This IOC represents the NEF function in 5GC. For more 
    information about the NEF, see 3GPP TS 23.501.";
  reference "3GPP TS 28.541";
  
  revision 2020-11-05 { reference CR-0412 ; }
  revision 2019-10-20 { reference "initial revision"; }
  
  grouping NEFFunctionGrp {
    description "Represents the NEFFunction IOC";
    uses mf3gpp:ManagedFunctionGrp;
    
    leaf sBIFQDN {
      description "The FQDN of the registered NF instance in the 
        service-based interface.";
      type inet:domain-name;
    }
    
    list sNSSAIList {
      description "List of S-NSSAIs the managed object is capable of supporting.
        (Single Network Slice Selection Assistance Information)
        An S-NSSAI has an SST (Slice/Service type) and an optional SD
        (Slice Differentiator) field.";
      key "sd sst";
      uses types5g3gpp:SNssai;
    }

    leaf-list capabilityList {
      description "List of supported capabilities of the NEF.";
      reference "3GPP TS 23.003";
      type string;
    }

    leaf isINEF {
      type boolean;
    }
    
    leaf isCAPIFSup {
      type boolean;
    }
    
  }
  
  augment "/me3gpp:ManagedElement" {
    list NEFFunction {
      description "5G Core NEF Function";
      reference "3GPP TS 28.541";
      key id;
      uses top3gpp:Top_Grp;
      container attributes {
        uses NEFFunctionGrp;
      }
    }
  }
}
