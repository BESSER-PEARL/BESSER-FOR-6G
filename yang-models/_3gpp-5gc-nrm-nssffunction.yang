module _3gpp-5gc-nrm-nssffunction {
  yang-version 1.1;
  
  namespace urn:3gpp:sa5:_3gpp-5gc-nrm-nssffunction;
  prefix nssf3gpp;
  
  import _3gpp-common-managed-function { prefix mf3gpp; }
  import _3gpp-common-managed-element { prefix me3gpp; }
  import ietf-inet-types { prefix inet; }
  import _3gpp-common-yang-types { prefix types3gpp; }
  import _3gpp-common-top { prefix top3gpp; }
  import _3gpp-5g-common-yang-types { prefix types5g3gpp; }
  
  organization "3gpp SA5";
  contact "https://www.3gpp.org/DynaReport/TSG-WG--S5--officials.htm?Itemid=464";
  description "This IOC represents the NSSF function in 5GC. For more 
    information about the NSSF, see 3GPP TS 23.501.";
  reference "3GPP TS 28.541";
  
  revision 2020-11-05 { reference CR-0412 ; }
  revision 2020-08-03 { reference "CR-0321"; }
  revision 2019-10-25 { reference "S5-194457 S5-195427 S5-193518"; }
  revision 2019-05-15 { reference "initial revision"; }
  
  grouping NSSFFunctionGrp {
    description "Represents the NSSFFunction IOC";
    uses mf3gpp:ManagedFunctionGrp;
    
    list pLMNIdList {
      description "List of at most six entries of PLMN Identifiers, but at least 
        one (the primary PLMN Id).
        The PLMN Identifier is composed of a Mobile Country Code (MCC) and a 
        Mobile Network Code (MNC).";

      min-elements 1;
      max-elements 6;
      key "mcc mnc";
      uses types3gpp:PLMNId;
    }
    
    leaf sBIFQDN {
      description "The FQDN of the registered NF instance in the service-based 
        interface.";
      type inet:domain-name;
    }
    
    list sNSSAIList {
      description "List of S-NSSAIs the managed object is capable of supporting.
                   (Single Network Slice Selection Assistance Information)
                   An S-NSSAI has an SST (Slice/Service type) and an optional SD
                   (Slice Differentiator) field.";
      
      reference "3GPP TS 23.003";
      key "sd sst";
      uses types5g3gpp:SNssai;
    }
    
    leaf-list cNSIIdList {
      description "NSI ID. NSI ID is an identifier for identifying the Core 
        Network part of a Network Slice instance when multiple Network Slice 
        instances of the same Network Slice are deployed, and there is a need 
        to differentiate between them in the 5GC, see clause 3.1 of TS 23.501 
        and subclause 6.1.6.2.7 of 3GPP TS 29.531";
      type string;
    }
    
    list managedNFProfile {
      key idx;
      min-elements 1;
      max-elements 1;
      uses types3gpp:ManagedNFProfile;
    }
  }
  
  augment "/me3gpp:ManagedElement" {
    list NSSFFunction {
      description "5G Core NSSF Function";
      reference "3GPP TS 28.541";
      key id;
      uses top3gpp:Top_Grp;
      container attributes {
        uses NSSFFunctionGrp;
      }
      uses mf3gpp:ManagedFunctionContainedClasses;
    }
  }
}
