module _3gpp-nr-nrm-dpciconfigurationfunction {
  yang-version 1.1;
  namespace "urn:3gpp:sa5:_3gpp-nr-nrm-dpciconfigurationfunction";
  prefix "dpciconfigurationfunction3gpp";

  import _3gpp-common-subnetwork { prefix subnet3gpp; }
  import _3gpp-common-top { prefix top3gpp; }
  import _3gpp-nr-nrm-nrcellcu { prefix nrcellcu3gpp; }
  import _3gpp-nr-nrm-gnbcucpfunction { prefix gnbcucp3gpp; }
  import _3gpp-common-managed-element { prefix me3gpp; }

  organization "3GPP SA5";
  contact "https://www.3gpp.org/DynaReport/TSG-WG--S5--officials.htm?Itemid=464";
  description "Defines the YANG mapping of the DPCIConfigurationFunction Information Object Class
    (IOC) that is part of the NR Network Resource Model (NRM).";
  reference "3GPP TS 28.541 5G Network Resource Model (NRM)";

  revision 2021-01-25 { reference CR-0454 ; }
  revision 2020-11-25 { reference CR-0386 ; }
  revision 2020-05-08 { reference S5-203316; }


  grouping DPCIConfigurationFunctionGrp {
    description "Represents the DPCICONFIGURATIONFunction IOC.";
    reference "3GPP TS 28.541";
    uses top3gpp:Top_Grp;


    list nRPciList {
      key NRPci;
      description "This holds a list of physical cell identities that can be assigned to the NR cells. This attribute shall be supported if D-SON PCI configuration or domain Centralized SON PCI configuration function is supported.";
	  leaf NRPci {type int32;}
      container attributes {
         uses NRPciListGrp;
     }
    }


    leaf dPciConfigurationControl {
        description " This attribute determines whether the Distributed SON or Domain-Centralized SON PCI configuration Function is enabled or disabled.";
        type boolean;
    }

  }

  grouping NRPciListGrp {
    description "Represents the NR PCI list for the PCI configuration function.";

    leaf NRPci {
        description "This attribute determines the NR PCI.";
        type int32 { range "0..1007"; }
        units "1";
    }
  }


  augment "/me3gpp:ManagedElement/gnbcucp3gpp:GNBCUCPFunction/nrcellcu3gpp:NRCellCU" {
    if-feature nrcellcu3gpp:DPCIConfigurationFunction;
    uses DPCIConfigurationFunctionGrp;
    }
  augment "/me3gpp:ManagedElement" {
    if-feature me3gpp:DPCIConfigurationFunction;
    uses DPCIConfigurationFunctionGrp;
    }
  augment "/subnet3gpp:SubNetwork" {
    if-feature subnet3gpp:DPCIConfigurationFunction;
    uses DPCIConfigurationFunctionGrp;
    }
}
