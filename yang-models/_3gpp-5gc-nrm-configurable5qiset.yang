module _3gpp-5gc-nrm-configurable5qiset {
  yang-version 1.1;
  
  namespace urn:3gpp:sa5:_3gpp-5gc-nrm-configurable5qiset;
  prefix Conf5QIs3gpp;
  
  import _3gpp-common-top { prefix top3gpp; }
  import _3gpp-common-managed-element { prefix me3gpp; }
  import _3gpp-common-subnetwork { prefix subnet3gpp; }
  
  organization "3gpp SA5";
  contact "https://www.3gpp.org/DynaReport/TSG-WG--S5--officials.htm?Itemid=464";
  description "This IOC represents the non-standardized 5QIs, including 
    their QoS characteristics, that need to be pre-configured 
    (and configurable) to the 5G NFs.";
  reference "3GPP TS 28.541";

  revision 2020-08-03 { reference "CR-0321"; }
  revision 2020-06-03 { reference "CR-0286"; }

  grouping PacketErrorRate {
    leaf scalar {
      type uint32 {
        range 0..9 ;
      }
      mandatory true;
      description "The Packet Error Rate of a 5QI expressed as Scalar x 10-k 
        where k is the Exponent.";
    }
    leaf exponent {
      type uint32 {
        range 0..9 ;
      }
      mandatory true;
      description "The Packet Error Rate of a 5QI expressed as Scalar x 10-k, 
        where k is the Exponent.";
    }
  }

  grouping FiveQICharacteristics {
    leaf fiveQIValue {
      type uint32 {
        range 0..255 ;
      }
      mandatory true;
      description "Identifies the 5QI value.";
    }

    leaf resourceType {
      type enumeration {
        enum GBR;
        enum NON_GBR;
      }
      mandatory true;
      description "It indicates the Resource Type of a 5QI, as specified 
        in TS 23.501 ";
    }
    
    leaf priorityLevel {
      type uint32 {
        range 0..127 ;
      }
    }
    
    leaf packetDelayBudget {
      type uint32 {
        range 0..1023 ;
      }
      description "Indicates the Packet Delay Budget (in unit of 0.5ms)of a 5QI, 
        as specified in TS 23.501 ";
    }
    
    list packetErrorRate {
      key "scalar exponent";
      min-elements 0;
      max-elements 1;
      uses PacketErrorRate;
      reference "TS 23.501";
    }

    leaf averagingWindow {
      type uint32 {
        range 0..4095 ;
      }
      units ms;
      reference "TS 23.501";
    }
    
    leaf maximumDataBurstVolume {
      type uint32{
        range 0..4095 ;
      }
      units byte;
    }
  }

  grouping Configurable5QISetGrp {
    description "Represents the Configurable5QISet IOC.";
    list configurable5QIs {
      key "fiveQIValue";
      uses FiveQICharacteristics;
    }
  }    

  grouping Configurable5QISetSubtree {
    list Configurable5QISet {
      description "Specifies the non-standardized 5QIs, including their QoS 
        characteristics, that need to be pre-configured (and configurable) to 
        the 5G NFs, see 3GPP TS 23.501.";
      key id;
      uses top3gpp:Top_Grp;
      container attributes {
        uses Configurable5QISetGrp;
      }
    }  
  }
  
  augment "/subnet3gpp:SubNetwork" {
    uses Configurable5QISetSubtree;
  }

  augment "/me3gpp:ManagedElement" {
    uses Configurable5QISetSubtree;
  }
}
